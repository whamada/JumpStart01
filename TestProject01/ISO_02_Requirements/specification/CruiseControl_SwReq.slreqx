# CruiseControl_SwReq
This document describes a requirement specification for an automobile cruise control system. The cruise control system provides functionality to control the speed of the vehicle automatically.

## INF: System Overview (Container)

### INF01: Cruise Control Inputs (Informational)
The inputs to the cruise control system include:
· A "Cruise" button to activate cruise control.
· A "Cancel" button to temporarily deactivate cruise control navigation.
· A "Set" button to set vehicle speed when the cruise control system is enabled.
· A "Resume" button to reset the vehicle to the previous set speed.
· A "Increment" button to increase the vehicle speed.
· A "Decrement" button to decrease the vehicle speed.
· The current vehicle speed.
· The throttle value from the accelerator pedal.
· The brake position from the brake pedal.
· The key position (Lock, Acc, ON, Start).
· The gear position (Park, Neutral, Drive, Reverse).

### INF02: Cruise Control Mode Indicators (Informational)
There are two indicator lights on the instrument panel:
· A “CRUISE” indicator that turns on when the cruise control system is activated.
· A “SET” indicator that turns on when the cruise control system is regulating the vehicle speed.

### INF03: Cruise Control Modes (Informational)
There are three modes for the cruise control system:
· Disabled: The cruise control system is not enabled.
· Enabled: The cruise control system is operational and is ready to control the vehicle speed. The vehicle speed is still under the driver’s control at this point.
· Activated: The cruise control system has taken over the driver’s throttle control. The driver can increase the throttle value to a value greater than is specified by the cruise control system.

### INF04: Cruise Control Outputs (Informational)
In addition to the mode and indicator, the outputs to the cruise control system include:
· The target speed.
· The throttle command.

## FCN: Functional Requirements (Functional)

### FCN01: Enabling Cruise Control (Functional)
Cruise control is enabled when the following conditions are met:
· Vehicle speed is within the target speed range (40km/h – 100km/h).
· Key position is ON.
· Gear position is Drive.
· Cruise button is pushed while the cruise control mode is disabled.

### FCN03: Activating Cruise Control (Functional)
Cruise control is activated when the following conditions are met:
· Vehicle speed is in the target speed range (40-100 km/h).
· Gear position is Drive.
· Set button is pushed while cruise control mode is enabled.
The target speed is set to a current vehicle speed when the Set button is pushed while the cruise control mode is enabled.

### FCN04: Deactivating Cruise Control (Functional)
Cruise control is disabled when one or more of the following conditions are met:
· Vehicle speed is not in the target speed range (40-100 km/h).
· Brake pedal is pressed.
· Gear position is not Drive.
· Cancel button is pushed.
Deactivating actions override any other button operations except for the disabling operation.

### FCN05: Target Speed Increment (Functional)
While the cruise control mode is activated, the driver can increase the target speed by pushing the Set+ button. When the button is pressed and then released in less than 500ms, the target speed is increased by 1 km/h.

### FCN06: Target Speed Decrement (Functional)
While the cruise control mode is activated, the driver can decrease the target speed by pushing the Set- button. When the button is pressed and then released in less than 500ms, the target speed is decreased by 1 km/h.

### FCN07: Successive Target Speed Increment (Functional)
While the cruise control mode is activated, the driver can increase the target speed by pushing the Set+ button. When the button is depressed and held for 500ms, the target speed increases by 5km/h every second until the button is released.

### FCN08: Successive Target Speed Decrement (Functional)
While the cruise control mode is activated, the driver can decrease the target speed by pushing the Set- button. When the button is depressed and held for 500ms, the target speed decreases by 5km/h every second until the button is released.

### FCN09: Target Speed Override with Accelerator Pedal (Functional)
While the cruise control mode is activated, the driver can increase the target speed using the accelerator pedal. When the accelerator pedal is depressed by more than 15%, the cruise control system is temporarily disabled from controlling the engine throttle as the vehicle speed changes. When the accelerator pedal is depressed by less than 5%, the cruise control is returned to active mode with the target speed adjusted to the current vehicle speed.

### FCN10: Resuming Cruise Control (Functional)
Cruise control can be resumed after being deactivated. Cruise control is resumed to keep previously set target speed when the following conditions are met:
· Vehicle speed is in the target speed range (40-100 km/h)
· Gear position is Drive.
· Resume button is pushed while the cruise control mode is enabled.
· There was a transition from activated to enabled at least one time and the cruise control system is not disabled since then.

### FCN11: Throttle Value Calculation (Functional)
The cruise control system calculates the throttle value using a PID controller. Gain parameters are determined to satisfy the following conditions:
· If the cruise control mode is activated when current vehicle speed is 40km/h and the target speed is 60km/h, the vehicle speed is maintained at 60km/h +- 5% within 20 sec.
· If the cruise control mode is activated when current vehicle speed is 80km/h and the target speed is 60km/h, the vehicle speed is maintained at 60km/h +- 5% within 20 sec.

### FCN12: Cruise Control CRUISE Indicator (Functional)
Cruise control CRUISE indicator light is displayed whenever the cruise control mode is enabled. When the ignition switch transitions from OFF to On, the CRUISE indicator light is displayed for either 3 seconds or until the ignition switch is turned to CRANK.

### FCN13: Cruise Control SET Indicator (Functional)
Cruise control SET indicator light is displayed whenever the cruise control mode is activated.

### FCN02: Disabling Cruise Control (Functional)
Cruise control is disabled when one or more of the following are met:
· When the vehicle is started.
· Key position is set to any other position than ON.
· Gear position is not Drive.
· Cruise button is pushed while the cruise control mode is enabled or activated.
